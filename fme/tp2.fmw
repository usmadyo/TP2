FME workspace tp2.fmw

Parameters:
- SourceDataset_GEOJSON = https://donnees.montreal.ca/dataset/ab112a84-0661-4360-9573-652eed16beeb/resource/a90678ac-7ea7-464c-b615-e8f5cb9f527b/download/rsqa_secteurs.geojson   # Source GeoJSON File or URL
- SourceDataset_WMS_3 = http://sirius/erdas-iws/ogc/wms/?   # Source WMS (Web Map Service) URL
- SourceDataset_CSV2_14 = https://donnees.montreal.ca/dataset/3e9f7b96-3f25-4404-a5ad-22d9a31060e6/resource/ccd5a4b7-cbca-4f5f-a746-ad8c576af374/download/rsqa-indice-qualite-air-station.csv   # Source CSV (Comma Separated Value) File(s)
- SourceDataset_CSV2_16 = https://donnees.montreal.ca/dataset/3e9f7b96-3f25-4404-a5ad-22d9a31060e6/resource/9c7434e9-f5af-4154-991c-293fbd5cb626/download/rsqa-indice-qualite-air-secteur.csv   # Source CSV (Comma Separated Value) File(s)
- SourceDataset_GEOTIFF = https://donnees.montreal.ca/dataset/dbdfbdba-0725-470d-a23e-da69dbedc4e6/resource/b8aff0f2-2c7b-48f5-b937-2aef5d253e22/download/ilots-de-chaleur-2016.zip   # Source GeoTIFF File(s) or URL(s)
- DestDataset_POSTGIS_13 = GEO7630   # Connection
- DestDataset_POSTGIS_11 = GEO7630   # Connection
- SourceDataset_CSV2 = https://donnees.montreal.ca/dataset/3e9f7b96-3f25-4404-a5ad-22d9a31060e6/resource/a25fdea2-7e86-42ac-8301-ca77db3ff17e/download/rsqa-indice-qualite-air.csv   # Source CSV (Comma Separated Value) File(s)
- DestDataset_POSTGIS_17 = GEO7630   # Connection
- SourceDataset_LAS = http://depot.ville.montreal.qc.ca/geomatique/lidar_aerien/2015/299-5056_2015.laz   # Source ASPRS LAS File(s)
- DestDataset_POSTGIS_RASTER_3 = GEO7630   # Connection
- DestDataset_POSTGIS_10 = GEO7630   # Connection
- DestDataset_POSTGIS_12 = GEO7630   # Connection
- DestDataset_POSTGIS_14 = GEO7630   # Connection
- DestDataset_POSTGIS_16 = GEO7630   # Connection
- DestDataset_POSTGIS_RASTER = GEO7630   # Connection
- DestDataset_POSTGIS = GEO7630   # Connection
- SourceDataset_SHAPEFILE_3 = https://donnees.montreal.ca/dataset/fab160ae-c81d-46f8-8f92-4a01c10d4390/resource/183866d5-9027-456a-b0af-36b2e45c8aac/download/batiments_2d_2016_arrondissements.zip   # Source Esri Shapefile(s)
- SourceDataset_GEOJSON_3 = https://donnees.montreal.ca/dataset/36f48854-474b-43d2-a16d-a433da8a1447/resource/77e44cc1-56b1-4e83-871d-e3990565563f/download/canopee-2019.zip   # Source GeoJSON File or URL
- DestDataset_POSTGIS_15 = GEO7630   # Connection

Readers:
- GEOJSON_1: GEOJSON from $(SourceDataset_GEOJSON)
- WMS_2: WMS from $(SourceDataset_WMS_3)
- CSV2_8: CSV2 from $(SourceDataset_CSV2_14)
- CSV2_9: CSV2 from $(SourceDataset_CSV2_16)
- GEOTIFF_1: GEOTIFF from $(SourceDataset_GEOTIFF)
- CSV2_1: CSV2 from $(SourceDataset_CSV2)
- LAS_1: LAS from $(SourceDataset_LAS)
- SHAPEFILE_2: SHAPEFILE from $(SourceDataset_SHAPEFILE_3)
- GEOJSON_2: GEOJSON from $(SourceDataset_GEOJSON_3)

Writers:
- POSTGIS_2: POSTGIS to $(DestDataset_POSTGIS_13)
- POSTGIS_3: POSTGIS to $(DestDataset_POSTGIS_11)
- POSTGIS_4: POSTGIS to $(DestDataset_POSTGIS_17)
- POSTGIS_RASTER_2: POSTGIS_RASTER to $(DestDataset_POSTGIS_RASTER_3) in EPSG:3857
- POSTGIS_6: POSTGIS to $(DestDataset_POSTGIS_10)
- POSTGIS_7: POSTGIS to $(DestDataset_POSTGIS_12)
- POSTGIS_8: POSTGIS to $(DestDataset_POSTGIS_14)
- POSTGIS_9: POSTGIS to $(DestDataset_POSTGIS_16)
- POSTGIS_RASTER_1: POSTGIS_RASTER to $(DestDataset_POSTGIS_RASTER)
- POSTGIS_1: POSTGIS to $(DestDataset_POSTGIS)
- POSTGIS_5: POSTGIS to $(DestDataset_POSTGIS_15)

Note: Un peu de ménage
AttributeManager_6
    ATTR_TABLE:
      REMOVE latitude (real64)
      REMOVE longitude (real64)
      REMOVE X (real64)
      REMOVE Y (real64)
    -> AttributeRangeMapper
Note: Classifier les valeurs en 4 catégories (Bon, Acceptable, Mauvaiset N/D
AttributeRangeMapper
    IN_ATTR = valeur
    LUT = 51,100,51 .. 100,26,50,26 .. 50,1,25,1 .. 25,,,
    OUT_ATTR = classe
    -> IQA_Station (writer POSTGIS_4)
Ortho2022_mosaique_2022_SCRS.ecw: Inspector
Note: Merge les valeurs IQA par station avec les valeurs IQA détaillé par station pour avoir les coordonnées
FeatureMerger
    ATTR_ACCUM_MODE = Merge Supplier
    ATTR_CONFLICT_RES = Use Requestor
    IGNORE_NULLS = No
    JOIN_KEYS = @Value(stationId) @Value(stationId) AUTO
    MERGE_TYPE = Attributes and Geometry
    PROCESS_DUPS = NO
    REJECT_NULL_MISSING_KEYS = No
    SUPPLIERS_FIRST = No
    MERGED -> Reprojector_10
    <REJECTED> -> FeatureMerger__Rejected_
Note: Un peu de ménage
AttributeManager_5
    ATTR_TABLE:
      REMOVE latitude (real64)
      REMOVE longitude (real64)
      REMOVE X (real64)
      REMOVE Y (real64)
    -> AttributeRangeMapper_2
Note: Classifier les valeurs en 4 catégories (Bon, Acceptable, Mauvais et N/D
AttributeRangeMapper_2
    IN_ATTR = valeur
    LUT = 51,100,51 .. 100,26,50,26 .. 50,1,25,1 .. 25,,,
    OUT_ATTR = classe
    -> IQA_station_polluant (writer POSTGIS_9)
Note: Merge les valeurs IQA par secteur avec les secteurs géographiques
FeatureMerger_2
    ATTR_ACCUM_MODE = Merge Supplier
    ATTR_CONFLICT_RES = Use Requestor
    IGNORE_NULLS = No
    JOIN_KEYS = @Value(secteur) @Value(nom) AUTO
    MERGE_TYPE = Attributes and Geometry
    PROCESS_DUPS = NO
    REJECT_NULL_MISSING_KEYS = No
    SUPPLIERS_FIRST = No
    MERGED -> Reprojector_2
    <REJECTED> -> FeatureMerger_2__Rejected_
Note: Un peu de ménage
AttributeManager_4
    ATTR_TABLE:
      REMOVE id (int64)
      REMOVE lettre (buffer)
      REMOVE nom (buffer)
      SET_TO max (varchar(200)) = @max(@Value(valeur))
    USER_EXPOSED_ATTRIBUTES = max
    -> AttributeFilter
Note: Filter les valeurs par secteur
AttributeFilter
    ATTR_NAME = secteur
    ATTR_VALUES = <Empty>,<Missing>,<Null>,<Unfiltered>,Centre-ville,Est,Nord,Ouest
    Centre-ville -> StatisticsCalculator
    Est -> StatisticsCalculator_2
    Nord -> StatisticsCalculator_3
    Ouest -> StatisticsCalculator_4
Note: La station avec l'IQA le plus élevé par secteur détermine la ressoruce IQA par secteur
Note: Classifier les valeurs en 4 catégories (Bon, Acceptable, Mauvais et N/D
AttributeRangeMapper_3
    IN_ATTR = valeur.max
    LUT = 51,100,51 .. 100,26,50,26 .. 50,1,25,1 .. 25,,,
    OUT_ATTR = classe
    -> rsqa_IQA_secteur_3857 (writer POSTGIS_8)
rsqa_IQA_secteur_3857 (writer POSTGIS_8)
    attributes: secteur varchar(12), valeur int8, date date, heure int8, max varchar(200), valeur_max int8, classe varchar
AttributeManager_2
    ATTR_TABLE:
      REMOVE calque (varchar(20))
      REMOVE projection (varchar(50))
      REMOVE reference (varchar(30))
      REMOVE EQM_plani (varchar(20))
      REMOVE EQM_alti (varchar(10))
      REMOVE MAJ (varchar(20))
      REMOVE methode (varchar(20))
      REMOVE source (varchar(100))
      REMOVE producteur (varchar(50))
      REMOVE version (real64)
    -> carto_bat_cote (writer POSTGIS_6)
AttributeManager_3
    ATTR_TABLE:
      REMOVE calque (varchar(20))
      REMOVE projection (varchar(50))
      REMOVE reference (varchar(30))
      REMOVE EQM_plani (varchar(20))
      REMOVE EQM_alti (varchar(10))
      REMOVE MAJ (varchar(20))
      REMOVE methode (varchar(20))
      REMOVE source (varchar(100))
      REMOVE producteur (varchar(50))
      REMOVE version (real64)
    -> carto_bat_toit (writer POSTGIS_7)
AttributeManager_7
    ATTR_TABLE:
      REMOVE calque (buffer)
      REMOVE projection (buffer)
      REMOVE reference (buffer)
      REMOVE EQM_plani (buffer)
      REMOVE EQM_alti (buffer)
      REMOVE MAJ (buffer)
      REMOVE methode (buffer)
      REMOVE VERSION (buffer)
    -> canope2019 (writer POSTGIS_5)

Bookmark: Reader des données brutes
Note: ilots_de_chaleur_2016 en format GEOTIFF
GEOTIFF (reader GEOTIFF_1)
    -> Reprojector_12
Note: IQA par station en temps réel (Quotidien)
CSV (reader CSV2_8)
    attributes: stationId uint32, adresse varchar(49), latitude y_coordinate, longitude x_coordinate, X real64, Y real64, polluant varchar(3), valeur uint32, date date, heure uint32
    -> FeatureMerger [SUPPLIER]
    -> Reprojector_13
Note: RSQA - Secteurs géographiques
rsqa_secteurs_4326 (reader GEOJSON_1)
    attributes: id int, lettre string, nom string
    -> FeatureMerger_2 [SUPPLIER]
Note: Ortho2022_mosaique_2022_SCRS.ecw: ? [WMS]
Note: http://sirius/erdas-iws/ogc/wms/?
Ortho2022_mosaique_2022_SCRS.ecw (reader WMS_2)
    attributes: wms_service_name memo, wms_service_title memo, wms_service_abstract memo, wms_layer_name memo, wms_layer_title memo, wms_layer_abstract memo, wms_selected_layers set(Ortho2022_mosaique_2022_SCRS.ecw)
    -> Ortho2022_mosaique_2022_SCRS.ecw
    -> Reprojector_9
Note: IQA détaillé par station en temps réel (Quotidien)
CSV (reader CSV2_1)
    attributes: stationId uint32, polluant varchar(3), valeur uint32, date date, heure uint32
    -> FeatureMerger [REQUESTOR]
Note: IQA par secteur en temps réel (Quotidien)
CSV (reader CSV2_9)
    attributes: secteur varchar(12), valeur uint32, date date, heure uint32
    -> FeatureMerger_2 [REQUESTOR]
Note: Données vectorielles avec une variable 3D format libre
canopee-2019 (reader GEOJSON_2)
    attributes: calque string, projection string, reference string, EQM_plani string, EQM_alti string, MAJ string, methode string, source string, producteur string, VERSION string
    -> EsriReprojector_3

Bookmark: REPROJECT vers EPSG:3857
Reprojector_12
    DEST = EPSG:3857
    INTERPOLATION_TYPE_NAME = Nearest Neighbor
    RASTER_CELL_SIZE = Preserve Cells
    RASTER_TOLERANCE = 0.0
    REPROJECTED -> RasterToPolygonCoercer
    REPROJECTED -> RasterSharpener
    REPROJECTED -> RasterCellCoercer
Reprojector_13
    DEST = EPSG:3857
    INTERPOLATION_TYPE_NAME = Nearest Neighbor
    RASTER_CELL_SIZE = Preserve Cells
    RASTER_TOLERANCE = 0.0
    REPROJECTED -> AttributeManager_6
Reprojector_9
    DEST = EPSG:3857
    INTERPOLATION_TYPE_NAME = Nearest Neighbor
    RASTER_CELL_SIZE = Preserve Cells
    RASTER_TOLERANCE = 0.0
    REPROJECTED -> ortho2022 (writer POSTGIS_RASTER_1)
Reprojector_10
    DEST = EPSG:3857
    INTERPOLATION_TYPE_NAME = Nearest Neighbor
    RASTER_CELL_SIZE = Preserve Cells
    RASTER_TOLERANCE = 0.0
    REPROJECTED -> AttributeManager_5
FeatureMerger__Rejected_: Logger
    LOG_FEATURE = LOG_ONLY
    MAXCOORDS = 20
    MAXFEATS = 20
    MESSAGE = Feature is:
    SEVERITY = INFO
Reprojector_2
    DEST = EPSG:3857
    INTERPOLATION_TYPE_NAME = Nearest Neighbor
    RASTER_CELL_SIZE = Preserve Cells
    RASTER_TOLERANCE = 0.0
    REPROJECTED -> AttributeManager_4
FeatureMerger_2__Rejected_: Logger
    LOG_FEATURE = LOG_ONLY
    MAXCOORDS = 20
    MAXFEATS = 20
    MESSAGE = Feature is:
    SEVERITY = INFO
Reprojector_11
    DEST = EPSG:3857
    INTERPOLATION_TYPE_NAME = Nearest Neighbor
    RASTER_CELL_SIZE = Preserve Cells
    RASTER_TOLERANCE = 0.0
    REPROJECTED -> AttributeManager_2
Reprojector_16
    DEST = EPSG:3857
    INTERPOLATION_TYPE_NAME = Nearest Neighbor
    RASTER_CELL_SIZE = Preserve Cells
    RASTER_TOLERANCE = 0.0
    REPROJECTED -> AttributeManager_3
Note: Reproject vers EPSG:3857
EsriReprojector_3
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> AttributeManager_7

Bookmark: Intégration de raster analytique - Ilôts de chaleur
Note: Convertir l'image raster en entités vectorielles polygonales
RasterToPolygonCoercer
    EXTRACT_NODATA = No
    LABEL_ATTRIBUTE = classification
    PRESERVE_ATTRIBUTES = Yes
    POLYGONS -> ilots_chaleur_polygones (writer POSTGIS_1)
    <REJECTED> -> RasterToPolygonCoercer__Rejected_
ilots_chaleur_polygones (writer POSTGIS_1)
    attributes: classification varchar
RasterToPolygonCoercer__Rejected_: Logger
    LOG_FEATURE = LOG_ONLY
    MAXCOORDS = 20
    MAXFEATS = 20
    MESSAGE = Feature is:
    SEVERITY = INFO
Note: Améliorer la netteté de l'image raster
RasterSharpener
    PRESERVE_BAND_INTERPRETATION = No
    SHARPENING_FACTOR = 3.0
    SHARPENING_FILTER_MODE = Fine
    SHARPENING_ITERATIONS = 5
    SHARPENED -> RasterCellValueRounder
    <REJECTED> -> RasterSharpener__Rejected_
RasterCellValueRounder
    PLACES = 1
    ROUND_TYPE = Nearest
    -> RasterToPolygonCoercer_2
    <REJECTED> -> RasterCellValueRounder__Rejected_
RasterToPolygonCoercer_2
    EXTRACT_NODATA = No
    LABEL_ATTRIBUTE = classification
    PRESERVE_ATTRIBUTES = Yes
    POLYGONS -> ilots_chaleur_sharp_polygones (writer POSTGIS_2)
    <REJECTED> -> RasterToPolygonCoercer_2__Rejected_
ilots_chaleur_sharp_polygones (writer POSTGIS_2)
    attributes: classification varchar
RasterToPolygonCoercer_2__Rejected_: Logger
    LOG_FEATURE = LOG_ONLY
    MAXCOORDS = 20
    MAXFEATS = 20
    MESSAGE = Feature is:
    SEVERITY = INFO
RasterCellValueRounder__Rejected_: Logger
    LOG_FEATURE = LOG_ONLY
    MAXCOORDS = 20
    MAXFEATS = 20
    MESSAGE = Feature is:
    SEVERITY = INFO
RasterSharpener__Rejected_: Logger
    LOG_FEATURE = LOG_ONLY
    MAXCOORDS = 20
    MAXFEATS = 20
    MESSAGE = Feature is:
    SEVERITY = INFO
RasterCellCoercer
    CELL_GEOMETRY = Points
    EXTRACT_BAND_VALUES_AS = Z Values
    EXTRACT_NODATA = No
    PRESERVE_ATTRIBUTES = Yes
    -> ilots_chaleur_points (writer POSTGIS_3)
    <REJECTED> -> RasterCellCoercer__Rejected_
ilots_chaleur_points (writer POSTGIS_3)
RasterCellCoercer__Rejected_: Logger
    LOG_FEATURE = LOG_ONLY
    MAXCOORDS = 20
    MAXFEATS = 20
    MESSAGE = Feature is:
    SEVERITY = INFO

Bookmark: POSTGIS WRITERS
IQA_Station (writer POSTGIS_4)
    attributes: stationid int8, adresse varchar(49), polluant varchar(3), valeur int8, date date, heure int8, classe varchar
ortho2022 (writer POSTGIS_RASTER_1)
    attributes: wms_service_name varchar, wms_service_title varchar, wms_service_abstract varchar, wms_layer_name varchar, wms_layer_title varchar, wms_layer_abstract varchar, wms_selected_layers char(33)
IQA_station_polluant (writer POSTGIS_9)
    attributes: stationid int8, polluant varchar(3), valeur int8, date date, heure int8, adresse varchar(49), classe varchar
carto_bat_cote (writer POSTGIS_6)
    attributes: elevation float8
carto_bat_toit (writer POSTGIS_7)
    attributes: superficie float8
canope2019 (writer POSTGIS_5)
    attributes: source varchar, producteur varchar

Bookmark: Max IQA par secteur
StatisticsCalculator
    ATTR_ACCUM_MODE = None
    CALCULATION_MODE = NUMERIC
    FEAT_STATS = valeur,NUMERIC_MODE,,MAX,,,,,,,,,,,
    COMPLETE -> AttributeRangeMapper_3
StatisticsCalculator_2
    ATTR_ACCUM_MODE = None
    CALCULATION_MODE = NUMERIC
    FEAT_STATS = valeur,NUMERIC_MODE,,MAX,,,,,,,,,,,
    COMPLETE -> AttributeRangeMapper_3
StatisticsCalculator_3
    ATTR_ACCUM_MODE = None
    CALCULATION_MODE = NUMERIC
    FEAT_STATS = valeur,NUMERIC_MODE,,MAX,,,,,,,,,,,
    COMPLETE -> AttributeRangeMapper_3
StatisticsCalculator_4
    ATTR_ACCUM_MODE = None
    CALCULATION_MODE = NUMERIC
    FEAT_STATS = valeur,NUMERIC_MODE,,MAX,,,,,,,,,,,
    COMPLETE -> AttributeRangeMapper_3

Bookmark: Données vectorielles 2D format libre
CARTO-BAT-COTE (reader SHAPEFILE_2)
    attributes: calque varchar(20), projection varchar(50), reference varchar(30), EQM_plani varchar(20), EQM_alti varchar(10), MAJ varchar(20), methode varchar(20), source varchar(100), producteur varchar(50), elevation double, version double
    -> Reprojector_11
CARTO-BAT-TOIT (reader SHAPEFILE_2)
    attributes: calque varchar(20), projection varchar(50), reference varchar(30), EQM_plani varchar(20), EQM_alti varchar(10), MAJ varchar(20), methode varchar(20), source varchar(100), producteur varchar(50), superficie double, version double
    -> Reprojector_16

Bookmark: Nuages de points lidar format .las (facultatif) pour la tuile de la station #55 / Read, Clean & Write to POSTGIS
LAS (reader LAS_1)
    -> PointCloudThinner
Note: Simplification du nuage de points
PointCloudThinner
    INTERVAL = 30
    THINNED -> EsriReprojector_2
    <REJECTED> -> PointCloudThinner__Rejected_
Note: Reproject vers EPSG:3857
EsriReprojector_2
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> PointCloudThinner_2
Note: Simplification du nuage de points
PointCloudThinner_2
    INTERVAL = 5
    THINNED -> PointCloudPropertyExtractor
    <REJECTED> -> PointCloudThinner_2__Rejected_
Note: Extraction des propriétés du nuage de points
PointCloudPropertyExtractor
    CALCULATE_EXTENTS_DISPLAY = No
    POINT_COMPONENTS = x  PROPERTIES MINMAX y  PROPERTIES MINMAX z  PROPERTIES MINMAX color_red  PROPERTIES  color_green  PROPERTIES  color_blue  PROPERTIES  classification  PROPERTIES
    -> AttributeManager
    <REJECTED> -> PointCloudPropertyExtractor__Rejected_
Note: Un peu de nettoyage
AttributeManager
    ATTR_TABLE:
      REMOVE _x_scale (real64)
      REMOVE _x_offset (real64)
      REMOVE _x_encoding (varchar(200))
      REMOVE _x_type (varchar(200))
      REMOVE _y_scale (real64)
      REMOVE _y_offset (real64)
      REMOVE _y_encoding (varchar(200))
      REMOVE _y_type (varchar(200))
      REMOVE _z_scale (real64)
      REMOVE _z_offset (real64)
      REMOVE _z_encoding (varchar(200))
      REMOVE _z_type (varchar(200))
      REMOVE _color_red_scale (real64)
      REMOVE _color_red_offset (real64)
      REMOVE _color_red_encoding (varchar(200))
      REMOVE _color_red_type (varchar(200))
      REMOVE _color_green_scale (real64)
      REMOVE _color_green_offset (real64)
      REMOVE _color_green_encoding (varchar(200))
      REMOVE _color_green_type (varchar(200))
      REMOVE _color_blue_scale (real64)
      REMOVE _color_blue_offset (real64)
      REMOVE _color_blue_encoding (varchar(200))
      REMOVE _color_blue_type (varchar(200))
      REMOVE _classification_scale (real64)
      REMOVE _classification_offset (real64)
      REMOVE _classification_encoding (varchar(200))
    -> PointCloudStatsRasterizer [PointCloud]
Note: Point cloud to Raster
PointCloudStatsRasterizer
    BACKGROUND_VALUE = -9999
    COMPONENT = classification
    FILL_WITH_NODATA = Yes
    MODE = number of points
    NUM_HORIZONTAL_TILES = 1
    NUM_VERTICAL_TILES = 1
    X_CELL_SIZE = 1
    Y_CELL_SIZE = 1
    Raster -> lidar2015 (writer POSTGIS_RASTER_2)
    <Rejected> -> PointCloudStatsRasterizer__Rejected_
lidar2015 (writer POSTGIS_RASTER_2)
    attributes: _x_min float8, _x_max float8, _y_min float8, _y_max float8, _z_min float8, _z_max float8, _classification_type varchar(200), _num_points int8
PointCloudStatsRasterizer__Rejected_: Logger
    LOG_FEATURE = LOG_ONLY
    MAXCOORDS = 20
    MAXFEATS = 20
    MESSAGE = Feature is:
    SEVERITY = INFO
PointCloudPropertyExtractor__Rejected_: Logger
    LOG_FEATURE = LOG_ONLY
    MAXCOORDS = 20
    MAXFEATS = 20
    MESSAGE = Feature is:
    SEVERITY = INFO
PointCloudThinner_2__Rejected_: Logger
    LOG_FEATURE = LOG_ONLY
    MAXCOORDS = 20
    MAXFEATS = 20
    MESSAGE = Feature is:
    SEVERITY = INFO
PointCloudThinner__Rejected_: Logger
    LOG_FEATURE = LOG_ONLY
    MAXCOORDS = 20
    MAXFEATS = 20
    MESSAGE = Feature is:
    SEVERITY = INFO

FME custom transformer PointCloudStatsRasterizer
Replaces a point cloud with a raster which represents statistical values of a component of the source point cloud.
This transformer computes a cell value based on the component value of every point within the cell. Supported components are:
z
intensity
number_of_returns
angle
classification
and supported statistical value types are:
minimum
maximum
median
average
standard deviation (sample)
standard deviation (population)
range
number of points *this value is common to every component
If the geometry of the input feature is not a point cloud, or the specified component does not exist in the source point cloud, or a parameter value is not valid, the input feature will be output via the <Rejected> port.
Usage Note
1. The processing with this transformer requires huge memory space when the number of points in the source point cloud is very large. In the worst case, the translation might be aborted by memory overflow. If memory overflow could occur, try setting 2 or more to the 'Number of Horizontal/Vertical Tiles' parameter so that the transformer splits the source point cloud into several parts with tiling operation in the intermediate process. The resulting raster will not be tiled even if you set 2 or more to the parameters.
2. The resulting raster will have a single band and its interpretation type will always be Real64. Consider using the RasterBandInterpretationCoercer to change the interpretation type later, if necessary.
3. Supported components are limited as listed above, but you can also use any other component to rasterize if you overwrite one of the supported components (e.g. 'z') by the target component value beforehand using the PointCloudExpressionEvaluator. 
4. Although this transformer performs rasterizing with (probably) the best effort in the current FME framework, the performance is worse than some tools specialized to point cloud operations such as LASTools (lasgrid.exe). If the performance is very much critical, consider using the LAStools.lasgrid custom transformer (FME Hub), which uses the LASTools (lasgrid.exe) internally.
5. This transformer does not require any other software installation and licensing than FME product, whereas the LASTools (lasgrid.exe) requires licensing to use commercially. This may be an advantage of this transformer (I think that it would be ideal if the NumericRasterizer would be improved so that it could perform statistical rasterizing efficiently).
6. This transformer contains a Python script, which was tested with both Python 2.7 and  Python 3.4 interpreter.
Parameters
    Component to Rasterize
    : 
    Select a component that should be used to perform statistical rasterizing. 
    Statistics Calculation Mode
    : 
    Select a statistical value type that should be computed as cell values.
    X Cell Spacing
    : 
    Specify the horizontal size of cells for the destination raster. 
    Y Cell Spacing
    : 
    Specify the vertical size of cells for the destination raster.
    Background Value
    : 
    Specify a value for cells in which there was no point. 
    Fill Background with Nodata
    : 
    Set 'Yes' if you need to flag the specified Background Value as the Nodata, set 'No' otherwise. 
    Number of Horizontal Tiles (Intermediate Tiling)
    :
    See 'Usage Note'. 
    Number of Vertical Tiles (Intermediate Tiling)
    :
    See 'Usage Note'.

Parameters:
- COMPONENT = z   # Component to Rasterize
- MODE = minimum   # deviation (sample)"%"standard deviation (population)"%range%"number of points" Statistics Calculation Mode
- X_CELL_SIZE = 1   # X Cell Spacing
- Y_CELL_SIZE = 1   # Y Cell Spacing
- BACKGROUND_VALUE = -9999   # Background Value
- FILL_WITH_NODATA = Yes   # Fill Background with Nodata
- NUM_HORIZONTAL_TILES = 1   # Number of Horizontal Tiles (Intermediate Tiling)
- NUM_VERTICAL_TILES = 1   # Number of Vertical Tiles (Intermediate Tiling)

PointCloud (input)
    -> GeometryFilter
Counter
    CNT_ATTR = __pcrasterizer.local_id
    DOMAIN = counter_local_id
    SCOPE = Global
    START = 0
    -> PointCloudTransformationApplier
    -> GeometryRemover
GeometryRemover
    REMOVE_COORDSYS = No
    -> FeatureMerger [REQUESTOR]
Note: PointCloudTransformationApplier
PointCloudTransformationApplier
    APPLY_MATRIX = Yes
    COMPONENTS_TO_APPLY = x,y,z,intensity,number_of_returns,angle,classification
    -> PointCloudExpressionEvaluator
Note: move (x, y) to nearest cell center, / replace z with specified component
PointCloudExpressionEvaluator
    EXPRESSION_TABLE = x Preserve (@floor(@Component(x)/$(X_CELL_SIZE))+0.5)*$(X_CELL_SIZE) y Preserve (@floor(@Component(y)/$(Y_CELL_SIZE))+0.5)*$(Y_CELL_SIZE) z Preserve @Component($(COMPONENT))
    RESULT -> PointCloudComponentKeeper
Note: keep (x, y, z)
PointCloudComponentKeeper
    COMPONENTS_TO_KEEP = x,y,z
    -> ParameterFetcher
ParameterFetcher
    ATTR_LIST = _mode {$(MODE)}
    -> Tiler
Tiler
    BOUNDARY_CASES = No
    COL_ATTR = _column
    NUM_HORIZONTAL_TILES = $(NUM_HORIZONTAL_TILES)
    NUM_VERTICAL_TILES = $(NUM_VERTICAL_TILES)
    ROW_ATTR = _row
    TILING_TYPE = Number of Tiles
    TILED -> PointCloudCoercer
Note: PointCloud -> Single Multipoint
PointCloudCoercer
    ACCUM_ATTRS_NAME = Yes
    CONVERT_TO_DISPLAY = Single Multipoint
    COERCED -> PythonCaller
Note: Multipoint -> 3D Line
PythonCaller
    PYTHONSOURCE:
      # 2016-06-23, Takashi Iijima, Original Implementation

      import fme, fmeobjects, math
      class PointCloudSourceCreator(object):
          def __init__(self):
              def getMedian(values):
                  values.sort()
                  n = len(values)
                  m = n//2
                  return values[m] if n%2 else (values[m-1]+values[m])*0.5

              def getStdDevSample(values):
                  a = sum(values)/len(values)
                  n = len(values)-1
                  return math.sqrt(sum([(v-a)**2 for v in values])/n) if 0 < n else 0

              def getStdDevPopulation(values):
                  a = sum(values)/len(values)
                  return math.sqrt(sum([(v-a)**2 for v in values])/len(values))

              self.statsFunctions = {
                  'minimum': min,
                  'maximum': max,
                  'median': getMedian,
                  'average': lambda values: sum(values)/len(values),
                  'standard deviation (sample)': getStdDevSample,
                  'standard deviation (population)': getStdDevPopulation,
                  'range': lambda values: max(values)-min(values),
                  'number of points': len,
              }

          def input(self, feature):
              cells = {} # key: tuple (x, y), value: list of component values
              for x, y, v in [p.getXYZ() for p in feature.getGeometry()]:
                  cells.setdefault((x, y), []).append(v)

              stats = self.statsFunctions[feature.getAttribute('_mode')]
              coords = [(x, y, stats(values)) for (x, y), values in cells.items()]
              feature.setGeometry(fmeobjects.FMELine(coords))
              self.pyoutput(feature)
    PYTHONSYMBOL = PointCloudSourceCreator
    -> PointCloudCombiner
Note: 3D Line -> PointCloud
PointCloudCombiner
    ACCUM_ATTRS_NAME = Get Attributes From One Representative Feature
    EXTRACT_RASTER_NODATA_NAME = No
    GROUP_BY = __pcrasterizer.local_id
    SPACING = 1.0
    -> NumericRasterizer
Note: PointCloud -> Raster
NumericRasterizer
    ANTI_ALIASING = No
    BACKGROUND_VALUE = $(BACKGROUND_VALUE)
    FILL_WITH_NODATA = $(FILL_WITH_NODATA)
    GROUP_BY = __pcrasterizer.local_id
    INTERPRETATION_TYPE = Real64
    ROWCOL_OR_CELLSIZE = CellSize
    SPECIFY_GROUND_EXTENTS = Use input data ground extents
    TOLERANCE = 0.5
    X_CELL_SIZE = $(X_CELL_SIZE)
    Y_CELL_SIZE = $(Y_CELL_SIZE)
    RASTER -> FeatureMerger [SUPPLIER]
Note: Restore Original Attributes
FeatureMerger
    JOIN_KEYS = @Value(__pcrasterizer.local_id) @Value(__pcrasterizer.local_id) AUTO
    MERGE_TYPE = Geometry
    PROCESS_DUPS = No
    REJECT_NULL_MISSING_KEYS = No
    SUPPLIERS_FIRST = No
    MERGED -> Raster (output)
Raster (output)
<Rejected> (output)

Bookmark: Validate Geometry Type and Parameter Values
GeometryFilter
    BREAK_AGG = No
    GEOM_PORT_NAMES = "Point Cloud"
    POINTCLOUD -> PointCloudPropertyExtractor
    <UNFILTERED> -> <Rejected> (output)
PointCloudPropertyExtractor
    ATTR_PREFIX = _exist
    CALCULATE_EXTENTS_DISPLAY = No
    POINT_COMPONENTS = x EXISTENCE   y EXISTENCE   z EXISTENCE   intensity EXISTENCE   number_of_returns EXISTENCE   angle EXISTENCE   classification EXISTENCE
    -> Tester
Tester
    BOOL_OP = COMPOSITE
    COMPOSITE_TEST = "1 AND 2 AND 3 AND 4 AND 5 AND 6 AND 7 AND ((8 AND 9) OR (10 AND 11) OR (12 AND 13) OR (14 AND 15) OR (16 AND 17))"
    TEST_CLAUSE:
      TEST 0 < $(X_CELL_SIZE)
      TEST 0 < $(Y_CELL_SIZE)
      TEST 0 < $(NUM_HORIZONTAL_TILES)
      TEST 0 < $(NUM_VERTICAL_TILES)
      TEST $(MODE) IN minimum,maximum,median,average,standard deviation (sample),standard deviation (population),range,number of points
      TEST @Value(_exist_x) = Yes
      TEST @Value(_exist_y) = Yes
      TEST $(COMPONENT) = z
      TEST @Value(_exist_z) = Yes
      TEST $(COMPONENT) = intensity
      TEST @Value(_exist_intensity) = Yes
      TEST $(COMPONENT) = number_of_returns
      TEST @Value(_exist_number_of_returns) = Yes
      TEST $(COMPONENT) = angle
      TEST @Value(_exist_angle) = Yes
      TEST $(COMPONENT) = classification
      TEST @Value(_exist_classification) = Yes
    TEST_MODE = Automatic
    PASSED -> Counter
    FAILED -> <Rejected> (output)
